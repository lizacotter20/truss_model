(defun jointslice (p1b p1t p2t insert p2b d_r / smth e1 e2 n n1 n2 rad nu_1 nu_2 )
	(print "GOT IN JOINTSLICE")
	(print p1b)
	(print p1t)
	(print p2t)
	(print insert)
	(print p2b)
	(print d_r)
	(setq smth (scale p2t -1.0))
	(print "MADE smth?")
	;vectors along the two rods
	(setq e1 (add p1b (scale p1t -1.0)))
	(print "MADE E1?")
	
	(setq e2 (add p1b smth))
	(print "made the e vectors")
	;calculate two vectors; 1 normal to each rod
	(setq n (cross e1 e2))
	(command "_line" p1b n "")
	(print "MADE N?")
	(setq n1 (cross n e1))
	(command "_line" p1b n1 "")
	(print "MADE N1?")
	(setq n2 (cross e2 n))
	(command "_line" p1b n2 "") 
	(print "CROSSED")
	;change the length of these vectors to the diameter of the rod 
	(setq rad (/ d_r 2.0))
	(setq nu_1 (scale (normalize n1) rad))
	(setq nu_2 (scale (normalize n2) rad))
	(print "NORMALIZED")
	;calculating the point where the rods intersect
	(setq factor1 (/ 1.0 (- (/ (cadr e2) (cadr e1)) (/ (car e2) (car e1)))))
	(setq factor2 (- (/ (- (car nu_1) (car nu_2)) (car e1)) (/ (- (cadr nu_1) (cadr nu_2)) (cadr e1))))
	(setq t4 (* factor1 factor2))
	(print "calculated t4!")
	;(setq t3 (+ (/ (- (car nu_1) (car nu_2)) (car e1)) (* (/ (car e2) (car e1)) t4)))
	(setq intersectionpt (add nu_2 (scale e2 t4)))
	;finding 3 points on the plane that slices the joints 
	(setq insert_h (list (car insert) (cadr insert) (caddr intersectionpt)))
	(setq p2b_h (list (car p2b) (cadr p2b) (caddr intersectionpt)))
	(command "_slice" p1b p1t p2t "" "3points" intersectionpt p2b_h insert_h "both")
	(print "sliced!!!!!")
	(command "_pline" intersectionpt insert_h p2b_h "")
	;(setq test (list 1 2 3))
	;(scale test -1)
)
